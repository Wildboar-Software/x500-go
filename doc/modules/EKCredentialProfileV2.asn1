-- // TODO: Assign an OID
EKCredentialProfileV2
DEFINITIONS
EXPLICIT TAGS
EXTENSIBILITY IMPLIED
::=
BEGIN

EXPORTS ALL;

IMPORTS

    ATTRIBUTE
        FROM InformationFramework
        {joint-iso-itu-t ds(5) module(1) informationFramework(1) 9}
        WITH SUCCESSORS

    AlgorithmIdentifier{}, SupportedAlgorithms
        FROM AuthenticationFramework
        {joint-iso-itu-t ds(5) module(1) authenticationFramework(7) 9}
        WITH SUCCESSORS

    ;

-- Object Identifiers

-- TCG specific OIDs
tcg OBJECT IDENTIFIER ::= {joint-iso-itu-t(2) international-organizations(23) tcg(133)}

tcg-attribute                   OBJECT IDENTIFIER ::= {tcg 2}
tcg-kp                          OBJECT IDENTIFIER ::= {tcg 8}

-- TCG Attribute OIDs
tcg-at-tpmManufacturer          OBJECT IDENTIFIER ::= {tcg-attribute 1}
tcg-at-tpmModel                 OBJECT IDENTIFIER ::= {tcg-attribute 2}
tcg-at-tpmVersion               OBJECT IDENTIFIER ::= {tcg-attribute 3}
tcg-at-tpmSpecification         OBJECT IDENTIFIER ::= {tcg-attribute 16}
tcg-at-tpmSecurityAssertions    OBJECT IDENTIFIER ::= {tcg-attribute 18}

-- TCG Key Purposes OIDs
tcg-kp-EKCertificate            OBJECT IDENTIFIER ::= {tcg-kp 1}

-- Values

-- // TODO: Specification uses STRMAX which is invalid name for a value.
strmax                          INTEGER ::= 256
urimax                          INTEGER ::= 1024
certstrmax                      INTEGER ::= 100000

-- Types

Version ::= INTEGER { v1(0) }

TPMSecurityAssertions ::= SEQUENCE {
    version                         Version DEFAULT v1,
    fieldUpgradable                 BOOLEAN DEFAULT FALSE,
    ekGenerationType                [0] IMPLICIT EKGenerationType OPTIONAL,
    ekGenerationLocation            [1] IMPLICIT EKGenerationLocation OPTIONAL,
    ekCertificateGenerationLocation [2] IMPLICIT EKCertificateGenerationLocation OPTIONAL,
    ccInfo                          [3] IMPLICIT CommonCriteriaMeasures OPTIONAL,
    fipsLevel                       [4] IMPLICIT FIPSLevel OPTIONAL,
    iso9000Certified                [5] IMPLICIT BOOLEAN DEFAULT FALSE,
    iso9000Uri                      IA5STRING (SIZE (1..urimax)) OPTIONAL -- // FIXME: Missing last paren
}

EKGenerationType ::= ENUMERATED {
    internal (0),
    injected (1),
    internalRevocable(2),
    injectedRevocable(3),
    firmwareLimited(4)
}

EKGenerationLocation ::= ENUMERATED {
    tpmManufacturer (0),
    platformManufacturer (1),
    ekCertSigner (2)
}

EKCertificateGenerationLocation ::= ENUMERATED {
    tpmManufacturer (0),
    platformManufacturer (1),
    ekCertSigner (2)
}

-- common criteria evaluation
CommonCriteriaMeasures ::= SEQUENCE {
    version                 IA5STRING (SIZE (1..strmax)), -- “2.2” or “3.1”; future syntax defined by CC
    assurancelevel          EvaluationAssuranceLevel,
    evaluationStatus        EvalutionStatus,
    plus                    BOOLEAN DEFAULT FALSE,
    strengthOfFunction      [0] IMPLICIT StrengthOfFunction OPTIONAL,
    profileOid              [1] IMPLICIT OBJECT IDENTIFIER OPTIONAL,
    profileUri              [2] IMPLICIT URIReference OPTIONAL,
    targetOid               [3] IMPLICIT OBJECT IDENTIFIER OPTIONAL,
    targetUri               [4] IMPLICIT URIReference OPTIONAL
}

EvaluationAssuranceLevel ::= ENUMERATED {
    levell (1),
    level2 (2),
    level3 (3),
    level4 (4),
    level5 (5),
    level6 (6),
    level7 (7)
}

StrengthOfFunction ::= ENUMERATED {
    basic (0),
    medium (1),
    high (2)
}

-- Reference to external document containing information relevant to this subject.
-- The hashAlgorithm and hashValue MUST both exist in each reference if either
-- appear at all.
URIReference ::= SEQUENCE {
    uniformResourceIdentifier   IA5String (SIZE (1..urimax)), -- // FIXME: Missing last paren
    hashAlgorithm               AlgorithmIdentifier{{SupportedAlgorithms}} OPTIONAL,
    hashValue                   BIT STRING OPTIONAL
}

EvaluationStatus ::= ENUMERATED {
    designedToMeet (0),
    evaluationInProgress (1),
    evaluationCompleted (2)
}

-- fips evaluation
FIPSLevel ::= SEQUENCE {
    version     IA5STRING (SIZE (1..strmax)), -- “140-1” or “140-2”
    level       SecurityLevel,
    plus        BOOLEAN DEFAULT FALSE
}

SecurityLevel ::= ENUMERATED {
    level1 (1),
    level2 (2),
    level3 (3),
    level4 (4)
}

TPMSpecification ::= SEQUENCE {
    family      UTF8String (SIZE (1..strmax)),
    level       INTEGER,
    revision    INTEGER
}

-- Attribute Types

tPMSecurityAssertions ATTRIBUTE ::= {
    WITH SYNTAX     TPMSecurityAssertions
    ID              tcg—at-tpmSecurityAssertions
}

-- // FIXME: Capitalized attributes
tpmManufacturer ATTRIBUTE ::= {
    WITH SYNTAX     UTF8String (SIZE (1..strmax))
    ID              tcg-at-tpmManufacturer
}

tpmModel ATTRIBUTE ::= {
    WITH SYNTAX     UTF8String (SIZE (1..strmax))
    ID              tcg-at-tpmModel
}

tpmVersion ATTRIBUTE ::= {
    WITH SYNTAX     UTF8String (SIZE (1..strmax))
    ID              tcg-at-tpmVersion
}

tpmSpecification ATTRIBUTE ::= {
    WITH SYNTAX     TPMSpecification
    ID              tcg-at-tpmSpecification
}

END
